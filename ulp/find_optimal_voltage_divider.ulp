// This ULP will find the best standard resistor values that match the desired
// voltage divider characteristics.
//
// Author: Tim Kostka <kostka@gmail.com>
// Created: January 28, 2018

// print an error message and exit
void error_out(string message) {
    message = ":We have encountered an error.\n\n" + message;
    dlgMessageBox(message);
    exit(1);
}

// voltage on the top rail
real top_rail = 16.8;

// target voltage on the middle rail
real mid_rail = 3.0;

// voltage at the bottom rail (usually 0 for ground)
real bottom_rail = 0.0;

// target impedance
string target_impedance_label = "100K";

// the relative weight of the impedance vs the ratio when calculating errors
//real impedance_importance = 0.1;
real target_impedance_importance = 0.1;

// impedance selection option
// 0 = R1 + R2
// 1 = 1/(1/R1+1/R2)
//int impedance_selection = 0;
int target_impedance_selection = 0;

// the default tolerance for each resistor series
real resistor_series_tolerances[] = {0.0, 0.10, 0.05, 0.02, 0.01};

// resistor series selections
int resistor_series_selection = 2;

// If 1, will include all E24 values in higher level series.  Note that E24 is
// not a subset of the higher level series.
int include_e24_values = 1;

// tolerance values for each selection
real tolerance_values[] = {0.0, 0.10, 0.05, 0.02, 0.01};

// tolerance selection
int tolerance_selection = 0;

// if 1, use the custom tolerance value
int custom_tolerance_selection = 0;

// custom tolerance value in %
real custom_tolerance = 5;

// schematic picture
string schematic_label = "<img src=find_optimal_voltage_divider.png>";

string results_target_impedance_label = "";
string results_r1_label = "";
string results_r2_label = "";
string results_ratio_label = "";
string results_impedance_1_label = "";
string results_impedance_2_label = "";
string results_current_label = "40 mA";
string results_target_ratio_label = "";
string results_mid_voltage_label = "";

// read a string resistance value and return the resistance in ohms
// return -1 if not recognized
real read_resistance(string value) {
    // value to return if not recognized
    real unrecognized_value = -1.0;
    // multiple character
    string multiplier_string = "RKM";
    char multiplier_character[] = {'R', 'K', 'M'};
    real multiplier_value[] = {1.0, 1000.0, 1000000.0};
    real multiplier = -1.0;
    // split by spaces into words
    string words[];
    strsplit(words, strupr(value), ' ');
    int word_count = 0;
    while (words[word_count] != "") {
        ++word_count;
    }
    // if more than 2 words, it's not recognized
    if (word_count > 2) {
        return unrecognized_value;
    }
    // if two words, second word should be multiplier
    if (word_count == 2) {
        if (strlen(words[1]) != 1) {
            return unrecognized_value;
        }
        int index = strchr(multiplier_string, words[1][0]);
        if (index == -1) {
            return unrecognized_value;
        }
        multiplier = multiplier_value[index];
    }
    // see if word 1 contains the multiplier
    int word_one_contains_multiplier = 0;
    int i;
    for (i = 0; i < strlen(multiplier_string); ++i) {
        int index = strchr(words[0], multiplier_string[i]);
        if (index >= 0) {
            if (multiplier != -1.0) {
                return unrecognized_value;
            }
            word_one_contains_multiplier = 1;
            multiplier = multiplier_value[i];
            // if it's at the end, remove it
            // else convert it to a decimal point
            if (index == strlen(words[0]) - 1) {
                words[0] = strsub(words[0], 0, index);
            } else {
                words[0][index] = '.';
            }
        }
    }
    // at this point, we either have a multiplier or we can set it to 1.0
    if (multiplier == -1.0) {
        multiplier = 1.0;
    }
    // make sure each character is a digit or a decimal point
    // and count number of decimals present
    int decimal_count = 0;
    for (i = 0; i < strlen(words[0]); ++i) {
        if (words[0][i] == '.') {
            ++decimal_count;
        } else if (!isdigit(words[0][i])) {
            return unrecognized_value;
        }
    }
    if (decimal_count > 1) {
        return unrecognized_value;
    }
    // should have at least one number
    if (strlen(words[0]) - decimal_count == 0) {
        return unrecognized_value;
    }
    real new_value = strtod(words[0]) * multiplier;
    //printf("Value in: \"%s\"\n", value);
    //printf("Value out: %.17g\n", new_value);
    return new_value;
    // if a decimal point is present, remove it and find the divider factor
    /*
    real divider = 1.0;
    int index = strchr(words[0], '.');
    if (index != -1) {
        for (i = index + 1; i < strlen(words[0]); ++i) {
            words[0][i - 1] = words[0][i];
            divider *= 10.0;
        }
        words[0] = strsub(words[0], 0, strlen(words[0]) - 1);
    }
    // it's valid, so return the value
    return strtol(words[0]) * multiplier / divider;
    */
}

// values from 10 to 100 for the EIA E12 10% series
real resistor_values_e12[] = {10, 12, 15, 18, 22, 27, 33, 39, 47, 56, 68, 82};

// values from 10 to 100 for the EIA E24 5% series
real resistor_values_e24[] = {10, 11, 12, 13, 15, 16, 18, 20, 22, 24, 27, 30,
                              33, 36, 39, 43, 47, 51, 56, 62, 68, 75, 82, 91};

// values from 10 to 100 for the EIA E48 2% series
real resistor_values_e48[] = {10.0, 10.5, 11.0, 11.5, 12.1, 12.7, 13.3, 14.0,
                              14.7, 15.4, 16.2, 16.9, 17.8, 18.7, 19.6, 20.5,
                              21.5, 22.6, 23.7, 24.9, 26.1, 27.4, 28.7, 30.1,
                              31.6, 33.2, 34.8, 36.5, 38.3, 40.2, 42.2, 44.2,
                              46.4, 48.7, 51.1, 53.6, 56.2, 59.0, 61.9, 64.9,
                              68.1, 71.5, 75.0, 78.7, 82.5, 86.6, 90.9, 95.3};

// values from 10 to 100 for the EIA E96 1% series
real resistor_values_e96[] = {10.0, 10.2, 10.5, 10.7, 11.0, 11.3, 11.5, 11.8,
                              12.1, 12.4, 12.7, 13.0, 13.3, 13.7, 14.0, 14.3,
                              14.7, 15.0, 15.4, 15.8, 16.2, 16.5, 16.9, 17.4,
                              17.8, 18.2, 18.7, 19.1, 19.6, 20.0, 20.5, 21.0,
                              21.5, 22.1, 22.6, 23.2, 23.7, 24.3, 24.9, 25.5,
                              26.1, 26.7, 27.4, 28.0, 28.7, 29.4, 30.1, 30.9,
                              31.6, 32.4, 33.2, 34.0, 34.8, 35.7, 36.5, 37.4,
                              38.3, 39.2, 40.2, 41.2, 42.2, 43.2, 44.2, 45.3,
                              46.4, 47.5, 48.7, 49.9, 51.1, 52.3, 53.6, 54.9,
                              56.2, 57.6, 59.0, 60.4, 61.9, 63.4, 64.9, 66.5,
                              68.1, 69.8, 71.5, 73.2, 75.0, 76.8, 78.7, 80.6,
                              82.5, 84.5, 86.6, 88.7, 90.9, 93.1, 95.3, 97.6};

real resistor_values[];

// populate the resistor_values[] array with possible resistor values
// based on the current option selections
void populate_resistor_values() {
    // index of next entry
    int index = 0;
    resistor_values[index] = 0;
    // if exact values, no need to populate
    if (resistor_series_selection == 0) {
        return;
    }
    // loop through the multipliers for each decade
    for (real multiplier = 0.1; multiplier <= 10000; multiplier *= 10.0) {
        if (resistor_series_selection == 1) {
            for (int i = 0; resistor_values_e12[i] != 0.0; ++i) {
                resistor_values[index] = resistor_values_e12[i] * multiplier;
                ++index;
            }
        } else if (resistor_series_selection == 2) {
            for (int i = 0; resistor_values_e24[i] != 0.0; ++i) {
                resistor_values[index] = resistor_values_e24[i] * multiplier;
                ++index;
            }
        } else if (resistor_series_selection == 3) {
            for (int i = 0; resistor_values_e48[i] != 0.0; ++i) {
                resistor_values[index] = resistor_values_e48[i] * multiplier;
                ++index;
            }
        } else if (resistor_series_selection == 4) {
            for (int i = 0; resistor_values_e96[i] != 0.0; ++i) {
                resistor_values[index] = resistor_values_e96[i] * multiplier;
                ++index;
            }
        } else {
            error_out("Unexpected value");
        }
    }
    // if selected, add E24 values to the list
    if (include_e24_values && resistor_series_selection > 2) {
        int j = 0;
        for (int i = 0; resistor_values_e24[i] != 0.0; ++i) {
            real new_value = resistor_values_e24[i];
            while (resistor_values[j] < new_value && resistor_values[j] != 0) {
                ++j;
            }
            if (resistor_values[j] != new_value) {
                for (real multiplier = 0.1; multiplier <= 10000; multiplier *= 10.0) {
                    resistor_values[index] = new_value * multiplier;
                    ++index;
                }
            }
        }
    }
    // add the 1M resistor
    resistor_values[index] = 1000000.0;
    ++index;
    //output("C:/Users/tdkostk/Documents/temp/eagle_ulp_output.txt", "at") {
    //    for (int i = 0; resistor_values[i] != 0.0; ++i) {
    //    printf("%g\n", resistor_values[i]);
    //    }
    //}
    // set end of array with a 0 value
    resistor_values[index] = 0;
}

// return the given resistor value in a standard format
string format_resistance(real value) {
    string formatted_value;
    //int target_significant_figures = 2;
    if (value >= 1000000) {
        sprintf(formatted_value, "%dM%06d", int(value / 1000000), int(value) % 1000000);
    } else if (value >= 1000) {
        sprintf(formatted_value, "%dK%03d", int(value / 1000), int(value) % 1000);
    } else {
        sprintf(formatted_value, "%dR%06d", int(value), int((value - int(value)) * 1000000.0));
    }
    // remove trailing zeroes
    while (formatted_value[strlen(formatted_value) - 1] == '0') {
        formatted_value = strsub(formatted_value, 0, strlen(formatted_value) - 1);
    }
    // find location of first significant figure
    int i = 0;
    while (i < strlen(formatted_value) && (formatted_value[i] == '0' || !isdigit(formatted_value[i]))) {
        ++i;
    }
    // for zero, count the first 0 as a significant figure
    if (value == 0.0) {
        i = 0;
    }
    // count significant figures present
    /*
    int significant_figures = 0;
    while (i < strlen(formatted_value)) {
        if (isdigit(formatted_value[i])) {
            ++significant_figures;
        }
        ++i;
    }
    // add zeroes to get desired number of figures
    while (significant_figures < target_significant_figures) {
        formatted_value += "0";
        ++significant_figures;
    }
    */
    // find location of first and only alpha character
    i = 0;
    while (isdigit(formatted_value[i])) {
        ++i;
    }
    char multiplier = formatted_value[i];
    // format appropriately
    if (i == strlen(formatted_value) - 1) {
        formatted_value = strsub(formatted_value, 0, strlen(formatted_value) - 1);
    } else {
        formatted_value[i] = '.';
    }
    if (multiplier != 'R') {
        formatted_value += multiplier;
    }
    // double check that what we put out we parse to the input value
    real check_value = read_resistance(formatted_value);
    /*real error = (value == 0) ? check_value : abs(check_value / value - 1.0);
    if (error > 1e-12) {
        string message = "Formatted value does not match input.  To\n"
                         "avoid making an error, no values will be changed.";
        sprintf(message, "%s\n\nInput: %.17g", message, value);
        sprintf(message, "%s\nOutput: \"%s\"", message, formatted_value);
        sprintf(message, "%s\nParsed output: %.17g", message, check_value);
        error_out(message);
    }*/
    return formatted_value;
}

// format the current value
// use 3 significant figures
string format_current(real current) {
    real original_current = current;
    if (current == 0.0) {
        return "0.00 A";
    }
    string text = "";
    string units[] = {"A", "mA", "uA", "nA", "pA"};
    int this_unit = 0;
    while (current < 1.0 && units[this_unit + 1] != "") {
        current *= 1000.0;
        ++this_unit;
    }
    if (current < 1.0) {
        sprintf(text, "%g A", original_current);
        return text;
    }
    if (current >= 100.0) {
        sprintf(text, "%.0f", current + 0.5);
    } else if (current >= 10.0) {
        sprintf(text, "%.1f", current + 0.05);
    } else {
        sprintf(text, "%.2f", current + 0.005);
    }
    text += " ";
    text += units[this_unit];
    return text;
}


// report the given error and set labels to NA values
void report_input_error(string message) {
    results_r1_label = message;
    results_r2_label = message;
    results_target_impedance_label = message;
    results_ratio_label = message;
    results_mid_voltage_label = message;
    results_impedance_1_label = message;
    results_impedance_2_label = message;
    results_current_label = message;
    results_target_ratio_label = message;
}

// calculate new values and update labels
void calculate() {
    real error;
    real error_low;
    real error_high;
    real r1;
    real r2;
    // ensure rails are in the right order
    if (!(top_rail > bottom_rail && mid_rail > bottom_rail && top_rail > mid_rail)) {
        report_input_error("Invalid rail values.");
        return;
    }
    // calculate target ratio
    real target_ratio = (mid_rail - bottom_rail) / (top_rail - bottom_rail);
    // convert input values to real values
    real target_impedance = read_resistance(target_impedance_label);
    if (target_impedance == -1.0) {
        report_input_error("Invalid impedance value.");
        return;
    }
    // tolerance value on resistors
    real tolerance;
    if (custom_tolerance_selection == 1) {
        tolerance = custom_tolerance / 100.0;
    } else {
        if (tolerance_selection == 0) {
            tolerance = resistor_series_tolerances[resistor_series_selection];
        } else {
            tolerance = tolerance_values[tolerance_selection];
        }
    }
    // find resistor values
    if (resistor_series_selection == 0) {
        if (target_impedance_selection == 0) {
            r1 = target_impedance * (1.0 - target_ratio);
            r2 = target_impedance - r1;
        } else if (target_impedance_selection == 1) {
            // target
            // 1/Z = 1/R1+1/R2
            // ratio = R2 / (R1 + R2) -> R1 = R2 * (1 / ratio - 1)
            r2 = target_impedance / (1.0 - target_ratio);
            r1 = r2 * (1.0 / target_ratio - 1.0);
        } else {
            error_out("Unexpected value.");
        }
    } else {
        // populate resistor entries
        populate_resistor_values();
        // test each pair of values
        real best_error = 100.0;
        real best_r1 = 1.0;
        real best_r2 = 1.0;
        for (int r1_index = 0; resistor_values[r1_index] != 0.0; ++r1_index) {
            r1 = resistor_values[r1_index];
            for (int r2_index = 0; resistor_values[r2_index] != 0.0; ++r2_index) {
                r2 = resistor_values[r2_index];
                real trial_ratio = r2 / (r1 + r2);
                real trial_impedance;
                if (target_impedance_selection == 0) {
                    trial_impedance = r1 + r2;
                } else if (target_impedance_selection == 1) {
                    trial_impedance = 1.0 / (1.0 / r1 + 1.0 / r2);
                } else {
                    error_out("Unexpected value");
                }
                real ratio_error = trial_ratio / target_ratio - 1.0;
                real impedance_error = trial_impedance / target_impedance - 1.0;
                real combined_error = ratio_error * ratio_error +
                    impedance_error * impedance_error * target_impedance_importance;
                if (combined_error < best_error) {
                    best_r1 = r1;
                    best_r2 = r2;
                    best_error = combined_error;
                }
            }
        }
        r1 = best_r1;
        r2 = best_r2;
    }
    
    // format labels
    sprintf(results_target_ratio_label,
            "Target ratio = %.3f",
            target_ratio);
    sprintf(results_target_impedance_label,
            "Target impedance = %s\ncalculated as Z = %s",
            format_resistance(target_impedance),
            (target_impedance_selection == 0) ? "R1 + R2" : "1/(1/R1+1/R2)");
    sprintf(results_r1_label, "R1 = %s", format_resistance(r1));
    sprintf(results_r2_label, "R2 = %s", format_resistance(r2));
    if (tolerance != 0.0) {
        sprintf(results_r1_label, "%s +/- %g%%", results_r1_label, tolerance * 100.0);
        sprintf(results_r2_label, "%s +/- %g%%", results_r2_label, tolerance * 100.0);
    }
    real r1_low = r1 * (1.0 - tolerance);
    real r1_high = r1 * (1.0 + tolerance);
    real r2_low = r2 * (1.0 - tolerance);
    real r2_high = r2 * (1.0 + tolerance);
    real ratio = r2 / (r1 + r2);
    real ratio_low = r2 * (1.0 - tolerance) / (r1 * (1.0 + tolerance) + r2 * (1.0 - tolerance));
    real ratio_high = r2 * (1.0 + tolerance) / (r1 * (1.0 - tolerance) + r2 * (1.0 + tolerance));
    real mid_voltage = bottom_rail + ratio * (top_rail - bottom_rail);
    real mid_voltage_low = bottom_rail + ratio_low * (top_rail - bottom_rail);
    real mid_voltage_high = bottom_rail + ratio_high * (top_rail - bottom_rail);
    real current = (top_rail - bottom_rail) / (r1 + r2);
    real current_low = (top_rail - bottom_rail) / (r1_high + r2_high);
    real current_high = (top_rail - bottom_rail) / (r1_low + r2_low);
    sprintf(results_mid_voltage_label, "Voltage = %.3f", mid_voltage);
    sprintf(results_ratio_label, "Ratio = %.3f", ratio);
    if (tolerance != 0.0) {
        sprintf(results_ratio_label,
                "%s [%.3f to %.3f]",
                results_ratio_label,
                ratio_low,
                ratio_high);
        sprintf(results_mid_voltage_label,
                "%s [%.3f to %.3f]",
                results_mid_voltage_label,
                mid_voltage_low,
                mid_voltage_high);
    }
    results_mid_voltage_label += " V";
    if (resistor_series_selection != 0 && mid_rail != 0.0) {
        error = mid_voltage / mid_rail - 1.0;
        sprintf(results_mid_voltage_label,
                "%s\nError = %.2f%%",
                results_mid_voltage_label,
                error * 100.0);
        if (tolerance != 0.0) {
            error_low = mid_voltage_low / mid_rail - 1.0;
            error_high = mid_voltage_high / mid_rail - 1.0;
            sprintf(results_mid_voltage_label,
                    "%s [%.2f%% to %.2f%%]",
                    results_mid_voltage_label,
                    error_low * 100.0,
                    error_high * 100.0);
        }
    }
    if (resistor_series_selection != 0) {
        error = ratio / target_ratio - 1.0;
        sprintf(results_ratio_label, "%s\nError = %.2f%%", results_ratio_label, error * 100.0);
        if (tolerance != 0.0) {
            error_low = ratio_low / target_ratio - 1.0;
            error_high = ratio_high / target_ratio - 1.0;
            sprintf(results_ratio_label,
                    "%s [%.2f%% to %.2f%%]",
                    results_ratio_label,
                    error_low * 100.0,
                    error_high * 100.0);
        }
    }
    // impedance calculation #1
    real impedance_1 = r1 + r2;
    sprintf(results_impedance_1_label,
            "With Z = R1 + R2:\nImpedance = %s",
            format_resistance(impedance_1));
    if (tolerance != 0.0) {
        sprintf(results_impedance_1_label,
                "%s [%s to %s]",
                results_impedance_1_label,
                format_resistance(impedance_1 * (1.0 - tolerance)),
                format_resistance(impedance_1 * (1.0 + tolerance)));
    }
    if (target_impedance_selection == 0 && tolerance != 0.0) {
        sprintf(results_impedance_1_label,
                "%s\nError = %.2f%%",
                results_impedance_1_label,
                (impedance_1 / target_impedance - 1.0) * 100.0);
        if (tolerance != 0.0) {
            error_low = impedance_1 * (1.0 - tolerance) / target_impedance - 1.0;
            error_high = impedance_1 * (1.0 + tolerance) / target_impedance - 1.0;
            sprintf(results_impedance_1_label,
                    "%s [%.2f%% to %.2f%%]",
                    results_impedance_1_label,
                    error_low * 100.0,
                    error_high * 100.0);
        }
    }
    // impedance calculation #2
    real impedance_2 = 1.0 / (1.0 / r1 + 1.0 / r2);
    sprintf(results_impedance_2_label,
            "With Z = 1/(1/R1+1/R2)\nImpedance = %s",
            format_resistance(impedance_2));
    real impedance_2_low = 1.0 / (1.0 / r1_low + 1.0 / r2_low);
    real impedance_2_high = 1.0 / (1.0 / r1_high + 1.0 / r2_high);
    if (tolerance != 0.0) {
        sprintf(results_impedance_2_label,
                "%s [%s to %s]",
                results_impedance_2_label,
                format_resistance(impedance_2_low),
                format_resistance(impedance_2_high));
    }
    if (target_impedance_selection == 1 && tolerance != 0.0) {
        sprintf(results_impedance_2_label,
                "%s\nError = %.2f%%",
                results_impedance_2_label,
                (impedance_2 / target_impedance - 1.0) * 100.0);
        if (tolerance != 0.0) {
            error_low = impedance_2_low / target_impedance - 1.0;
            error_high = impedance_2_high / target_impedance - 1.0;
            sprintf(results_impedance_2_label,
                    "%s [%.2f%% to %.2f%%]",
                    results_impedance_2_label,
                    error_low * 100.0,
                    error_high * 100.0);
        }
    }
    sprintf(results_current_label,
            "Current draw = %s",
            format_current(current));
}

// perform calculation
calculate();

// bring up the main dialog box
int result = dlgDialog("Find voltage divider resistors") {
    dlgLabel("Change values as needed.  Press \"Perform calculation\" to update results.");
    dlgLabel("");
    dlgHBoxLayout{
        dlgGroup("Schematic view") {
            dlgLabel(schematic_label);
        }
        dlgLabel("  ");
        dlgStretch(1);
        dlgVBoxLayout{
            dlgGroup("Voltage values") {
                dlgHBoxLayout{dlgLabel("Top (V):"); dlgRealEdit(top_rail);dlgStretch(1);}
                dlgHBoxLayout{dlgLabel("Target mid (V):"); dlgRealEdit(mid_rail);dlgStretch(1);}
                dlgHBoxLayout{dlgLabel("Bottom (V):"); dlgRealEdit(bottom_rail);dlgStretch(1);}
            }
            dlgStretch(1);
            dlgGroup("Impedance options") {
                dlgHBoxLayout{
                    dlgLabel("Target impedance:");
                    dlgStringEdit(target_impedance_label);
                    dlgStretch(1);
                }
                dlgRadioButton("Calculated as R1 + R2", target_impedance_selection);
                dlgRadioButton("Calculated as 1/(1/R1 + 1/R2)", target_impedance_selection);
                dlgHBoxLayout{
                    dlgLabel("Relative importance:");
                    dlgRealEdit(target_impedance_importance);
                    dlgStretch(1);
                }
            }
            dlgStretch(1);
                dlgHBoxLayout{
            dlgGroup("Resistor series") {
                dlgRadioButton("Exact", resistor_series_selection);
                dlgRadioButton("EIA E12 (10%)", resistor_series_selection);
                dlgRadioButton("EIA E24 (5%)", resistor_series_selection);
                dlgRadioButton("EIA E48 (2%)", resistor_series_selection);
                dlgRadioButton("EIA E96 (1%)", resistor_series_selection);
                dlgCheckBox("Include E24 values\nin E48+ series", include_e24_values);
            }
            dlgGroup("Tolerance selection") {
                dlgRadioButton("From series", tolerance_selection);
                dlgRadioButton("10%", tolerance_selection);
                dlgRadioButton("5%", tolerance_selection);
                dlgRadioButton("2%", tolerance_selection);
                dlgRadioButton("1%", tolerance_selection);
            dlgStretch(1);
            dlgHBoxLayout{
                dlgCheckBox("Custom (%):", custom_tolerance_selection);
                dlgRealEdit(custom_tolerance);
                }
            }
            }
        }
        dlgLabel("  ");
        dlgStretch(1);
        dlgVBoxLayout{
            dlgStretch(1);
            dlgGroup("Results") {
                dlgLabel(results_target_ratio_label, 1);
                dlgLabel(results_target_impedance_label, 1);
                dlgLabel("");
                dlgLabel(results_r1_label, 1);
                dlgLabel(results_r2_label, 1);
                dlgLabel("");
                dlgLabel(results_mid_voltage_label, 1);
                dlgLabel(results_ratio_label, 1);
                dlgLabel(results_impedance_1_label, 1);
                dlgLabel(results_impedance_2_label, 1);
                dlgLabel(results_current_label, 1);
                dlgStretch(1);
            }
            dlgHBoxLayout{
                dlgStretch(1);
                dlgPushButton("+   Perform calculation   ") {calculate();};
                dlgStretch(1);
            }
            dlgStretch(1);
        }
    }
    dlgLabel("");
    dlgStretch(1);
    dlgHBoxLayout {
        dlgStretch(1);
        dlgPushButton("&Done") {dlgAccept(0);};
        dlgPushButton("-&Cancel") {dlgReject(1);};
    }
};
