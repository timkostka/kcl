// This ULP shows the standard resistor values for each EIA series.
//
// Author: Tim Kostka <kostka@gmail.com>
// Created: January 18, 2018

// values from 10 to 100 for the EIA E12 10% series
real resistor_values_e12[] = {10, 12, 15, 18, 22, 27, 33, 39, 47, 56, 68, 82};

// values from 10 to 100 for the EIA E24 5% series
real resistor_values_e24[] = {10, 11, 12, 13, 15, 16, 18, 20, 22, 24, 27, 30,
                              33, 36, 39, 43, 47, 51, 56, 62, 68, 75, 82, 91};

// values from 10 to 100 for the EIA E48 2% series
real resistor_values_e48[] = {10.0, 10.5, 11.0, 11.5, 12.1, 12.7, 13.3, 14.0,
                              14.7, 15.4, 16.2, 16.9, 17.8, 18.7, 19.6, 20.5,
                              21.5, 22.6, 23.7, 24.9, 26.1, 27.4, 28.7, 30.1,
                              31.6, 33.2, 34.8, 36.5, 38.3, 40.2, 42.2, 44.2,
                              46.4, 48.7, 51.1, 53.6, 56.2, 59.0, 61.9, 64.9,
                              68.1, 71.5, 75.0, 78.7, 82.5, 86.6, 90.9, 95.3};

// values from 10 to 100 for the EIA E96 1% series
real resistor_values_e96[] = {10.0, 10.2, 10.5, 10.7, 11.0, 11.3, 11.5, 11.8,
                              12.1, 12.4, 12.7, 13.0, 13.3, 13.7, 14.0, 14.3,
                              14.7, 15.0, 15.4, 15.8, 16.2, 16.5, 16.9, 17.4,
                              17.8, 18.2, 18.7, 19.1, 19.6, 20.0, 20.5, 21.0,
                              21.5, 22.1, 22.6, 23.2, 23.7, 24.3, 24.9, 25.5,
                              26.1, 26.7, 27.4, 28.0, 28.7, 29.4, 30.1, 30.9,
                              31.6, 32.4, 33.2, 34.0, 34.8, 35.7, 36.5, 37.4,
                              38.3, 39.2, 40.2, 41.2, 42.2, 43.2, 44.2, 45.3,
                              46.4, 47.5, 48.7, 49.9, 51.1, 52.3, 53.6, 54.9,
                              56.2, 57.6, 59.0, 60.4, 61.9, 63.4, 64.9, 66.5,
                              68.1, 69.8, 71.5, 73.2, 75.0, 76.8, 78.7, 80.6,
                              82.5, 84.5, 86.6, 88.7, 90.9, 93.1, 95.3, 97.6};
                              
// number of decimal places to print for each series
int series_decimal_places[] = {0, 0, 1, 1};

// current series selection
int resistor_series_selection = 1;

// values of resistors in this series
string series_values;

// update
void update_resistor_values() {
    series_values = "";
    int values_per_line = 8;
    string format;
    sprintf(format, "%%.%df", series_decimal_places[resistor_series_selection]);
    if (resistor_series_selection == 0) {
        for (int i = 0; resistor_values_e12[i] != 0.0; ++i) {
            if (i > 0 && i % values_per_line == 0) {
                series_values += "\n";
            } else if (i > 0) {
                series_values += "   ";
            }
            sprintf(series_values, "%s" + format, series_values, resistor_values_e12[i]);
        }
    } else if (resistor_series_selection == 1) {
        for (int i = 0; resistor_values_e24[i] != 0.0; ++i) {
            if (i > 0 && i % values_per_line == 0) {
                series_values += "\n";
            } else if (i > 0) {
                series_values += "   ";
            }
            sprintf(series_values, "%s" + format, series_values, resistor_values_e24[i]);
        }
    } else if (resistor_series_selection == 2) {
        for (int i = 0; resistor_values_e48[i] != 0.0; ++i) {
            if (i > 0 && i % values_per_line == 0) {
                series_values += "\n";
            } else if (i > 0) {
                series_values += "   ";
            }
            sprintf(series_values, "%s" + format, series_values, resistor_values_e48[i]);
        }
    } else if (resistor_series_selection == 3) {
        for (int i = 0; resistor_values_e96[i] != 0.0; ++i) {
            if (i > 0 && i % values_per_line == 0) {
                series_values += "\n";
            } else if (i > 0) {
                series_values += "   ";
            }
            sprintf(series_values, "%s" + format, series_values, resistor_values_e96[i]);
        }
    }
}

// initialize labels
update_resistor_values();

// show the dialog box with each label
dlgDialog("Standard resistor values") {
    dlgGroup("Resistor series") {
        dlgRadioButton("EIA E12 (10%)", resistor_series_selection) update_resistor_values();
        dlgRadioButton("EIA E24 (5%)", resistor_series_selection) update_resistor_values();
        dlgRadioButton("EIA E48 (2%)", resistor_series_selection) update_resistor_values();
        dlgRadioButton("EIA E96 (1%)", resistor_series_selection) update_resistor_values();
    }
    dlgLabel("");
    dlgGroup("Standard resistor values") {
        dlgLabel(series_values, 1);
    }
    dlgLabel("");
    dlgStretch(1);
    dlgHBoxLayout {
        dlgStretch(1);
        dlgPushButton("&Done") {dlgAccept(0);};
        dlgPushButton("-&Cancel") {dlgReject(1);};
    }
};
